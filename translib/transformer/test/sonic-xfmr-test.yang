module sonic-xfmr-test {
	namespace "http://github.com/Azure/sonic-xfmr-test";
	prefix sonic-xfmr-test;
	yang-version 1;

	organization
		"SONiC";

	contact
		"SONiC";

	description
		"SONIC transformer test yang";

	revision 2023-04-30 {
		description
			"Initial revision of Sonic transformer test yang.";
	}

	container sonic-xfmr-test {

		container TEST_SENSOR_GROUP {

			list TEST_SENSOR_GROUP_LIST {
				key "id";

				leaf id {
			            type string;
				}

				leaf-list colors {
					type string;
				}

        			leaf color-hold-time {
			            type uint32;
			            description "Hold time";
			        }
			}
		}

                container TEST_SENSOR_GROUP_COUNTERS {
			config false;

                        list TEST_SENSOR_GROUP_COUNTERS_LIST {
                                key "id";
                                
                                leaf id {
					type leafref {
						path "../../../TEST_SENSOR_GROUP/TEST_SENSOR_GROUP_LIST/id";
					}
                                }
                                
                                leaf frame-in {
                                    type uint32;
                                }

                                leaf frame-out {
                                    type uint32;
                                }
                        }
                }

		container TEST_SENSOR_A_TABLE {

			list TEST_SENSOR_A_TABLE_LIST { 
				key "id type";

				leaf id {
					type leafref {
						path "../../../TEST_SENSOR_GROUP/TEST_SENSOR_GROUP_LIST/id";
					}
				} 

				leaf type {
					type string {
			                        pattern "sensor_type_a_*" {
                        				error-message "Invalid sensor type";
				                        error-app-tag invalid-sensor-type;
						}
                        		}
				}

				leaf exclude_filter {
					type string;
				}

				leaf description_a {
					type string; 
				}
			}
		}

                container TEST_SENSOR_B_TABLE {

                        list TEST_SENSOR_B_TABLE_LIST {
                                key "id type";

                                leaf id {
                                        type leafref {
                                                path "../../../TEST_SENSOR_GROUP/TEST_SENSOR_GROUP_LIST/id";
                                        }
                                }

                               leaf type {
                                        type string {
                                                pattern "sensor_type_b_*" {
                                                        error-message "Invalid sensor type";
                                                        error-app-tag invalid-sensor-type;
                                                }
                                        }
                                }

                                leaf exclude_filter {
                                        type string;
                                }

                                leaf description_b {
                                        type string;
                                }
                        }
                }

                container TEST_SET_TABLE {

                        list TEST_SET_TABLE_LIST {
                                key "name";
                                
                                leaf name {
                                        type string;
                                }

				leaf type {
                                        type enumeration {
                                                enum IPV4; 
                                                enum IPV6;
                                        }
                                }

				leaf-list ports {
					type string;
				}       
                                
                                leaf description {
                                        type string;
                                }
                        }
                }

                container TEST_SENSOR_MODE_TABLE {

                        list TEST_SENSOR_MODE_TABLE_LIST {
                                key "mode";

                                leaf mode {
                                        type string;
                                }

                                leaf description {
                                        type string;
                                }
                        }
                }

	}
}
